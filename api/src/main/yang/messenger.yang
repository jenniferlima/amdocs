module messenger {
    yang-version 1;
    namespace "urn:opendaylight:params:xml:ns:yang:messenger";
    prefix "messenger";

    revision "2015-01-05" {
        description "Initial revision of messenger model";
    }
}
